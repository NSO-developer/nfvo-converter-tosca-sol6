module nfvo-solcon-tosca {

  namespace "http://tail-f.com/pkg/nfvo-solcon-tosca";
  prefix  nfvo-solcon-tosca;
  yang-version 1.1;

  import  nfvo-solcon-tosca { prefix solcon; }

  import ietf-inet-types {
    prefix inet;
  }
  import tailf-common {
    prefix tailf;
  }
  import tailf-ncs {
    prefix ncs;
  }

  description
    "Converter from TOSCA to SOL6";

  revision 2019-02-26 {
    description
      "First version";
  }

}
